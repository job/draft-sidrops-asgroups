RpkiSignedGroupingOptOut-2022
  { iso(1) member-body(2) us(840) rsadsi(113549)
    pkcs(1) pkcs9(9) smime(16) mod(0)
    id-mod-rpkiSignedGroupingOptOut-2022(TBD) }

DEFINITIONS EXPLICIT TAGS ::=
BEGIN

IMPORTS
  CONTENT-TYPE
  FROM CryptographicMessageSyntax-2010 -- in [RFC6268]
    { iso(1) member-body(2) us(840) rsadsi(113549) pkcs(1)
      pkcs-9(9) smime(16) modules(0) id-mod-cms-2009(58) }

  ASID, ASIdOrGroupingPointer, GroupingLabel
  FROM RpkiSignedGrouping-2022
    { iso(1) member-body(2) us(840) rsadsi(113549)
      pkcs(1) pkcs9(9) smime(16) mod(0)
      id-mod-rpkiSignedGrouping-2022(TBD) }

ct-rpkiSignedGroupingOptOut CONTENT-TYPE ::=
  { TYPE RpkiSignedGroupingOptOut
    IDENTIFIED BY id-ct-rpkiSignedGroupingOptOut }

id-ct-signedGroupingOptOut OBJECT IDENTIFIER ::=
  { iso(1) member-body(2) us(840) rsadsi(113549) pkcs(1)
    pkcs-9(9) id-smime(16) id-ct(1) TBD }

RpkiSignedGroupingOptOut ::= SEQUENCE {
  version [0]      INTEGER DEFAULT 0,
  asID             ASID,
  label            GroupingLabel (SIZE(1..100)) OPTIONAL,
  optOut           SEQUENCE (SIZE(0..MAX)) OF ASIdOrGroupingPointer }

END
